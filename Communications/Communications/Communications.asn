Module-order DEFINITIONS AUTOMATIC TAGS ::=
BEGIN

Message ::= CHOICE {
    request Request,
    response Response,
    ...
}

Request ::= SEQUENCE {

}

Response ::= SEQUENCE {
    health System-health,
    location Location,
    ...
}

System-health ::= ENUMERATED {
    nominal(0),
    ...
}

Location ::= SEQUENCE {
    latitude INTEGER (-90000000..90000000),
    longitude INTEGER(-180000000..180000000),
    altitude INTEGER(-500..36000000),
    ...
}

END
